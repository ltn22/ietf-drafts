module ietf-sid-file-extension {
  yang-version 1.1;
  namespace "urn:ietf:params:xml:ns:yang:ietf-sid-file-extension";
  prefix sid-ext;

  import ietf-sid-file {
    prefix sid;
    reference "RFC 9595";
  }

  import ietf-yang-structure-ext {
    prefix sx;
    reference "RFC 8791";
  }

  organization "Personal contribution";
  contact
    "Editor: Laurent Toutain
      <mailto:laurent.toutain@imt-atlantique.fr>

             Javier A. Fernandez
             <mailto:javier-alejandro.fernandez@imt-atlantique.fr>

             Vojtěch Vilímek
             <mailto:vojtech.vilimek@nic.cz>";
  description
    "Augmentation of ietf-sid-file to add type information
     per item and key-mapping at the sid-file level.";

  revision 2026-07-19 {
    description "IETF 126 Hackathon refinements";
  }

  revision 2026-04-28 {
    description "Initial revision.";
  }

  // it may be better if NETMOD created a YANG Module
  // with identities for built-in types

  identity yang-base-type {
    description "Base identity for all YANG built-in types.";
  }

  identity anydata {
    base yang-base-type;
    description "YANG built-in type anydata.";
  }

  identity anyxml {
    base yang-base-type;
    description "YANG built-in type anyxml.";
  }

  identity binary {
    base yang-base-type;
    description "YANG built-in type binary.";
  }

  identity boolean {
    base yang-base-type;
    description "YANG built-in type boolean.";
  }

  identity decimal64 {
    base yang-base-type;
    description "YANG built-in type decimal64.";
  }

  identity empty {
    base yang-base-type;
    description "YANG built-in type empty.";
  }

  identity identityref {
    base yang-base-type;
    description "YANG built-in type identityref.";
  }

  identity instance-identifier {
    base yang-base-type;
    description "YANG built-in type instance-identifier.";
  }

  identity int8 {
    base yang-base-type;
    description "YANG built-in type int8.";
  }

  identity int16 {
    base yang-base-type;
    description "YANG built-in type int16.";
  }

  identity int32 {
    base yang-base-type;
    description "YANG built-in type int32.";
  }

  identity int64 {
    base yang-base-type;
    description "YANG built-in type int64.";
  }

  identity leafref {
    base yang-base-type;
    description "YANG built-in type leafref.";
  }

  identity string {
    base yang-base-type;
    description "YANG built-in type string.";
  }

  identity uint8 {
    base yang-base-type;
    description "YANG built-in type uint8.";
  }

  identity uint16 {
    base yang-base-type;
    description "YANG built-in type uint16.";
  }

  identity uint32 {
    base yang-base-type;
    description "YANG built-in type uint32.";
  }

  identity uint64 {
    base yang-base-type;
    description "YANG built-in type uint64.";
  }

  identity union {
    base yang-base-type;
    description "YANG built-in type union.";
  }

  typedef yang-type {
    type identityref {
      base yang-base-type;
    }
    description
      "An identityref that selects one of the YANG built-in types
       defined in this module.";
  }

  // --- Augmentation 1: within the grouping, via its point of use ---
  sx:augment-structure "/sid:sid-file/sid:item" {
    // This augmentation targets the expanded list inside the /sid:sid-file/sid:item, 
    // the /sid:sid-file is sx:structure, not grouping (even through it is defined inside grouping)
    description
      "Adds type information to each SID item.";
    container type {
      leaf base-type {
        type yang-type;
      }
      leaf identityref {
        type uint64;
        description "SID of the referenced identity.";
      }
      container enumerate {
        leaf enum-value {
          type uint32;
          description "Value of the enumeration item.";
        }
        leaf enum-name {
          type string;
          description "Name of the enumeration item.";
        }
      }
      container bits {
        leaf bit-position {
          type uint32;
          description "Position of the bit item.";
        }
        leaf bit-name {
          type string;
          description "Name of the bit item.";
        }
      }
    }
  }
 
  // --- Augmentation 2: at the sid-file level, excluding items ---
  sx:augment-structure "/sid:sid-file" {
    description
      "Adds key-mapping at the sid-file level.";
    container key-mapping {
      description
        "Maps each list SID to the ordered list of SIDs
         of its key leaves.";
      list entry {
        key "list-sid";
        leaf list-sid {
          type sid:sid;
          description "SID of the list node.";
        }
        leaf-list key-sids {
          type sid:sid;
          ordered-by user;
          description "SIDs of the key leaves, in key order.";
        }
      }
    }
  }
}
